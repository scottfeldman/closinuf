# -*- coding: utf-8 -*-
"""Build X-running B-splines from slice sketches, then a Curves WB Gordon surface.

Prereqs: Run CreateCrossSections.FCMacro first. Slice sketches are found by attachment
to DatumPlane_X* on the Body (works even when FreeCAD renames the sketch to Sketch001).

Curves workbench (tomate44/Curves) must be installed.

Convention (Curves WB, two-source mode):
  Sources[0] = guides  = longitudinal curves (constant Y, varying X) — built here every Y_STEP.
  Sources[1] = profiles = slice / cross-section curves (constant X) — edges from each sketch.

So: slice sketches are profiles; the new X-direction splines are guides (not the other way around).

Output: Two Part::FeaturePython drivers plus Curves Gordon surface, all parented under the
same PartDesign Body as the slice sketches (required for in-scope PropertyLinkList).
Edit a slice sketch → recompute → surface updates.

Moving one sketch control point does not move the whole intersection grid automatically;
the grid is implicit (slice B-splines × Y-station guides). For a literal point grid in
the sketch, use Sketcher carbon-copy or construction geometry (not implemented here).
"""
import importlib
import re

import FreeCAD as App
import FreeCADGui as Gui
import Part

Y_STEP_MM = 50.0
Y_TOL_MM = 1e-4


def _active_body(doc):
    try:
        ad = Gui.ActiveDocument
        if ad and ad.ActiveView:
            b = ad.ActiveView.getActiveObject("pdbody")
            if b is not None:
                return b
    except Exception:
        pass
    for obj in doc.Objects:
        if obj.TypeId == "PartDesign::Body":
            return obj
    return None


def _sketch_in_body(sk, body):
    try:
        if sk.getParentGeoFeatureGroup() == body:
            return True
    except Exception:
        pass
    return sk in getattr(body, "Group", [])


def _sketch_attached_to_slice_datum(sk):
    sup = getattr(sk, "AttachmentSupport", None) or getattr(sk, "Support", None)
    if not sup:
        return False
    for ref, _sub in sup:
        if ref is None:
            continue
        rn = getattr(ref, "Name", "") or ""
        if rn.startswith("DatumPlane_X"):
            return True
    return False


def _slice_sketches(doc, body):
    """Slice sketches from CreateCrossSections: same Body, same datum naming.

    FreeCAD often renames object Name to Sketch001… while the tree shows a custom
    Label (e.g. Sketch_X00046). Matching only o.Name misses half the slices.
    Primary rule: sketch attached to DatumPlane_X* from the cross-section macro.
    Fallback: Name looks like Sketch_X… (optional _ before digits, optional -).
    """
    name_pat = re.compile(r"^Sketch_X_?-?\d+$")
    found = []
    for o in doc.Objects:
        if o.TypeId != "Sketcher::SketchObject":
            continue
        if not _sketch_in_body(o, body):
            continue
        if _sketch_attached_to_slice_datum(o) or name_pat.match(o.Name):
            found.append(o)
    found.sort(key=lambda sk: sk.Shape.BoundBox.XMin)
    return found


def _profile_edge(sk):
    eds = sk.Shape.Edges
    if len(eds) == 1:
        return eds[0]
    if len(eds) == 0:
        return None
    w = Part.Wire(eds)
    try:
        apx = w.approximate(1e-6, 1e-4, 25, 999)
        sh = apx.toShape()
        if sh.Edges:
            return sh.Edges[0]
    except Exception:
        pass
    return eds[0]


def _point_on_edge_at_y(edge, y_target):
    c = edge.Curve
    ta = edge.FirstParameter
    tb = edge.LastParameter
    pa = c.value(ta)
    pb = c.value(tb)
    ymin = min(pa.y, pb.y)
    ymax = max(pa.y, pb.y)
    if ymax - ymin < Y_TOL_MM:
        return App.Vector(pa.x, y_target, 0.5 * (pa.z + pb.z))
    y_use = max(ymin, min(ymax, y_target))
    if pa.y > pb.y:
        ta, tb = tb, ta
        pa, pb = pb, pa
    for _ in range(80):
        tm = 0.5 * (ta + tb)
        ym = c.value(tm).y
        if abs(ym - y_use) < Y_TOL_MM:
            return c.value(tm)
        if ym < y_use:
            ta = tm
        else:
            tb = tm
    return c.value(0.5 * (ta + tb))


def _y_stations(y0, y1, step=None):
    if step is None:
        step = Y_STEP_MM
    if y1 < y0:
        y0, y1 = y1, y0
    ys = [y0]
    y = y0 + step
    while y < y1 - 1e-6:
        ys.append(y)
        y += step
    if abs(ys[-1] - y1) > 1e-3:
        ys.append(y1)
    return ys


def _import_gordon():
    mod = importlib.import_module("freecad.Curves.gordonFP")
    return mod.gordonFP, mod.gordonVP


def _move_into_body(body, obj, after_feature=None):
    """Parent obj to PartDesign Body so links to sketches in that body are in scope."""
    if obj is None or body is None:
        return False
    try:
        if obj in list(getattr(body, "Group", []) or []):
            return True
    except Exception:
        pass
    add = getattr(body, "addObject", None)
    if callable(add):
        try:
            add(obj)
            return True
        except Exception:
            pass
    ins = getattr(body, "insertObject", None)
    if callable(ins):
        refs = []
        if after_feature is not None:
            refs.append(after_feature)
        refs.append(None)
        for ref in refs:
            for tail in (True, False):
                try:
                    ins(obj, ref, tail)
                    return True
                except Exception:
                    continue
    try:
        g = list(getattr(body, "Group", []) or [])
        if obj not in g:
            g.append(obj)
            body.Group = g
        return True
    except Exception as exc:
        App.Console.PrintWarning(
            "GordonHoodFromSlices: could not add %s to Body (%s).\n"
            % (getattr(obj, "Name", "?"), exc)
        )
        return False


def _sorted_slice_sketches(sketches):
    return sorted(sketches, key=lambda sk: sk.Shape.BoundBox.XMin)


def _build_profile_edges(sketches):
    sks = _sorted_slice_sketches(sketches)
    edges = []
    for sk in sks:
        if not sk.Shape or sk.Shape.isNull():
            continue
        e = _profile_edge(sk)
        if e is not None:
            edges.append(e)
    return edges


def _build_guide_shapes(sketches, y_step):
    sks = _sorted_slice_sketches(sketches)
    if len(sks) < 2:
        return []
    bb = sks[0].Shape.BoundBox
    for sk in sks[1:]:
        bb.add(sk.Shape.BoundBox)
    y0 = bb.YMin
    y1 = bb.YMax
    stations = _y_stations(y0, y1, float(y_step))
    shapes = []
    for y in stations:
        pts = []
        for sk in sks:
            edge = _profile_edge(sk)
            if edge is None:
                return []
            pts.append(_point_on_edge_at_y(edge, y))
        if len(pts) < 2:
            continue
        try:
            bs = Part.BSplineCurve()
            bs.interpolate(pts, False)
            shapes.append(bs.toShape())
        except Exception:
            shapes.append(Part.makePolygon(pts))
    return shapes


class _HoodProfilesDriverFP:
    """Compound of profile edges; Shape tracks linked slice sketches."""

    def __init__(self, obj):
        obj.addProperty(
            "App::PropertyLinkList",
            "SliceSketches",
            "Links",
            "Cross-section sketches (datum slice sketches)",
        )
        obj.Proxy = self

    def execute(self, obj):
        sks = obj.SliceSketches
        if not sks:
            obj.Shape = Part.Shape()
            return
        edges = _build_profile_edges(sks)
        if len(edges) < 2:
            obj.Shape = Part.Shape()
            return
        obj.Shape = Part.Compound(edges)

    def dumps(self):
        return None

    def loads(self, state):
        return None


class _HoodGuidesDriverFP:
    """Compound of X-running guide curves; tracks same sketches + YStep."""

    def __init__(self, obj):
        obj.addProperty(
            "App::PropertyLinkList",
            "SliceSketches",
            "Links",
            "Same slice sketches as profile driver",
        )
        obj.addProperty(
            "App::PropertyFloat",
            "YStep",
            "Grid",
            "Guide spacing along Y (mm)",
        )
        obj.YStep = float(Y_STEP_MM)
        obj.Proxy = self

    def execute(self, obj):
        sks = obj.SliceSketches
        step = float(getattr(obj, "YStep", Y_STEP_MM) or Y_STEP_MM)
        if not sks or step <= 0:
            obj.Shape = Part.Shape()
            return
        shapes = _build_guide_shapes(sks, step)
        if len(shapes) < 2:
            obj.Shape = Part.Shape()
            return
        obj.Shape = Part.Compound(shapes)

    def dumps(self):
        return None

    def loads(self, state):
        return None


class _DriverVP:
    def __init__(self, vobj):
        vobj.Proxy = self

    def attach(self, vobj):
        self.Object = vobj.Object

    def dumps(self):
        return None

    def loads(self, state):
        return None


def main():
    doc = App.activeDocument()
    if doc is None:
        App.Console.PrintError("GordonHoodFromSlices: no active document.\n")
        return

    body = _active_body(doc)
    if body is None:
        App.Console.PrintError(
            "GordonHoodFromSlices: no PartDesign Body (activate one in the tree).\n"
        )
        return

    sketches = _slice_sketches(doc, body)
    if len(sketches) < 2:
        App.Console.PrintError(
            "GordonHoodFromSlices: need at least two slice sketches (attached to DatumPlane_X* on the Body).\n"
        )
        return

    doc.recompute()

    try:
        gordon_fp_cls, gordon_vp_cls = _import_gordon()
    except Exception as exc:
        App.Console.PrintError(
            "GordonHoodFromSlices: Curves workbench not available (%s).\n" % (exc,)
        )
        return

    for sk in sketches:
        if not sk.Shape or sk.Shape.isNull():
            App.Console.PrintError(
                "GordonHoodFromSlices: sketch %s has no shape.\n" % (sk.Name,)
            )
            return
        if _profile_edge(sk) is None:
            App.Console.PrintError(
                "GordonHoodFromSlices: no edges in sketch %s.\n" % (sk.Name,)
            )
            return

    prof_edges = _build_profile_edges(sketches)
    guide_shapes = _build_guide_shapes(sketches, Y_STEP_MM)
    if len(prof_edges) < 2 or len(guide_shapes) < 2:
        App.Console.PrintError(
            "GordonHoodFromSlices: need at least two profiles and two guides.\n"
        )
        return

    bb = sketches[0].Shape.BoundBox
    for sk in sketches[1:]:
        bb.add(sk.Shape.BoundBox)
    y0 = bb.YMin
    y1 = bb.YMax

    gname = "HoodGordon_Guides"
    pname = "HoodGordon_Profiles"
    gordname = "HoodGordonSurface"
    for n in (gordname, gname, pname):
        old = doc.getObject(n)
        if old is not None:
            doc.removeObject(old.Name)

    guides_obj = doc.addObject("Part::FeaturePython", gname)
    _HoodGuidesDriverFP(guides_obj)
    _DriverVP(guides_obj.ViewObject)

    profiles_obj = doc.addObject("Part::FeaturePython", pname)
    _HoodProfilesDriverFP(profiles_obj)
    _DriverVP(profiles_obj.ViewObject)

    gordon = doc.addObject("Part::FeaturePython", gordname)
    gordon_fp_cls(gordon)
    gordon_vp_cls(gordon.ViewObject)

    # PartDesign link scope: document-level objects cannot link to sketches inside a Body.
    # Parent drivers + Gordon into the same Body as the slices, then assign links.
    sks_sorted = _sorted_slice_sketches(sketches)
    anchor = sks_sorted[-1] if sks_sorted else None
    for o in (guides_obj, profiles_obj, gordon):
        if not _move_into_body(body, o, anchor):
            App.Console.PrintError(
                "GordonHoodFromSlices: failed to add %s to Body — fix tree manually or "
                "use a Body that accepts Part::FeaturePython.\n" % (o.Name,)
            )
            return

    guides_obj.SliceSketches = sketches
    guides_obj.YStep = float(Y_STEP_MM)
    profiles_obj.SliceSketches = sketches
    gordon.Sources = [guides_obj, profiles_obj]
    doc.recompute()

    gv = getattr(guides_obj, "ViewObject", None)
    pv = getattr(profiles_obj, "ViewObject", None)
    if gv is not None:
        gv.Visibility = False
    if pv is not None:
        pv.Visibility = False

    App.Console.PrintMessage(
        "GordonHoodFromSlices: %d profiles, %d guides (Y every %g mm, %g..%g), Gordon=%s.\n"
        % (
            len(prof_edges),
            len(guide_shapes),
            Y_STEP_MM,
            y0,
            y1,
            gordon.Name,
        )
    )
    App.Console.PrintMessage(
        "Curves WB: Sources[0]=guides (X-running), Sources[1]=profiles (slices).\n"
    )
    App.Console.PrintMessage(
        "Parametric: HoodGordon_Profiles / HoodGordon_Guides link slice sketches — "
        "recompute (F5) after editing a sketch to refresh the surface. "
        "Adjust YStep on Guides to change longitudinal spacing.\n"
    )


main()
