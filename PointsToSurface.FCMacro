# -*- coding: utf-8 -*-
"""Point cloud → X-normal slice sketches → parametric Curves Gordon surface (one run).

Select the point cloud in the tree before running (required if the document has more than
one Points::Feature). If exactly one cloud exists, it is used when nothing is selected.
Uses or creates a PartDesign Body. Requires Curves WB
for the Gordon step. Drivers live in the Body (link scope). Edit sketches → F5 to refresh.
At run time you are prompted for guide spacing along Y (mm); the last value is remembered
(User parameter BaseApp/Macro/PointsToSurface, key YStep). You can also edit YStep on
GordonSurface_Guides after the fact.
Slice B-splines call exposeInternalGeometry so control points are available without using
Sketcher “show internal geometry” first (when the Sketcher build supports it).

Curves WB: Sources[0]=guides (X-running, YStep mm apart), Sources[1]=profiles (slices).
Guide points use each profile edge at the requested Y when that Y lies on the edge; otherwise
they lie on the straight line between the sampled Y-minimum and Y-maximum points on that edge
(slice plane), so out-of-range Y does not clamp to one vertex and guides stay well-behaved.
"""
import importlib
import re
from collections import defaultdict

import FreeCAD as App
import FreeCADGui as Gui
import Part

X_GROUP_TOL_MM = 0.5
Y_STEP_MM = 50.0
Y_TOL_MM = 1e-4
_PARAM_Y_STEP = "User parameter:BaseApp/Macro/PointsToSurface"


def _input_double_dialog(parent, title, label, default, minimum, maximum, decimals):
    try:
        from PySide2.QtWidgets import QInputDialog

        return QInputDialog.getDouble(
            parent, title, label, float(default), minimum, maximum, decimals
        )
    except ImportError:
        pass
    try:
        from PySide6.QtWidgets import QInputDialog

        return QInputDialog.getDouble(
            parent, title, label, float(default), minimum, maximum, decimals
        )
    except ImportError:
        pass
    try:
        from PySide.QtGui import QInputDialog

        return QInputDialog.getDouble(
            parent, title, label, float(default), minimum, maximum, decimals
        )
    except ImportError:
        pass
    return (float(default), True)


def _resolve_y_step_mm():
    """Default from Y_STEP_MM, then last-used from Param; GUI prompt when available."""
    pg = App.ParamGet(_PARAM_Y_STEP)
    stored = pg.GetFloat("YStep", 0.0)
    default = float(stored) if stored > 0 else float(Y_STEP_MM)
    try:
        mw = Gui.getMainWindow()
        if mw is not None:
            val, ok = _input_double_dialog(
                mw,
                "PointsToSurface",
                "Guide spacing along Y (mm) for Gordon:",
                default,
                0.1,
                500.0,
                2,
            )
            if not ok:
                return None
            val = float(val)
            if val <= 0:
                App.Console.PrintWarning(
                    "PointsToSurface: Y step must be positive; using %g mm.\n" % Y_STEP_MM
                )
                val = float(Y_STEP_MM)
            pg.SetFloat("YStep", val)
            return val
    except Exception:
        pass
    return default


def _active_body(doc, create_if_missing=False):
    try:
        ad = Gui.ActiveDocument
        if ad and ad.ActiveView:
            b = ad.ActiveView.getActiveObject("pdbody")
            if b is not None:
                return b
    except Exception:
        pass
    for obj in doc.Objects:
        if obj.TypeId == "PartDesign::Body":
            return obj
    if create_if_missing:
        body = doc.addObject("PartDesign::Body", "Body")
        doc.recompute()
        return body
    return None


def _new_partdesign_plane(body, name):
    for type_id in ("PartDesign::DatumPlane", "PartDesign::Plane"):
        try:
            return body.newObject(type_id, name)
        except Exception:
            continue
    raise RuntimeError("Could not create PartDesign datum plane object.")


def _extract_points(obj):
    pk = getattr(obj, "Points", None)
    if pk is None:
        return []
    if hasattr(pk, "getPoints"):
        try:
            pts, _normals = pk.getPoints(0)
            return [App.Vector(p) for p in pts]
        except Exception:
            pass
    n = getattr(pk, "CountPoints", None)
    if n is not None:
        out = []
        for i in range(int(n)):
            try:
                out.append(App.Vector(pk.getPoint(i)))
            except Exception:
                break
        if out:
            return out
    raw = getattr(pk, "Points", None)
    if isinstance(raw, (list, tuple)):
        return [App.Vector(p) for p in raw]
    shp = getattr(obj, "Shape", None)
    if shp and getattr(shp, "Vertexes", None):
        return [v.Point for v in shp.Vertexes]
    return []


def _pick_points_object(doc):
    try:
        sel = Gui.Selection.getSelection()
    except Exception:
        sel = []
    for o in sel:
        if o is None:
            continue
        tid = getattr(o, "TypeId", "")
        if "Points" not in tid and not (
            hasattr(o, "Points") and _extract_points(o)
        ):
            continue
        if not _extract_points(o):
            continue
        return o

    point_feats = []
    for o in doc.Objects:
        if "Points" not in getattr(o, "TypeId", ""):
            continue
        if _extract_points(o):
            point_feats.append(o)

    if len(point_feats) == 1:
        o = point_feats[0]
        App.Console.PrintMessage(
            "PointsToSurface: nothing selected — using sole point cloud %s.\n"
            % (getattr(o, "Label", None) or o.Name,)
        )
        return o
    if len(point_feats) > 1:
        App.Console.PrintError(
            "PointsToSurface: select one point cloud in the tree (%d in document).\n"
            % (len(point_feats),)
        )
        return None
    App.Console.PrintError(
        "PointsToSurface: no point cloud — import .asc (Points workbench) and select it.\n"
    )
    return None


def _group_by_x(vectors):
    buckets = defaultdict(list)
    for v in vectors:
        key = round(v.x / X_GROUP_TOL_MM) * X_GROUP_TOL_MM
        buckets[key].append(v)
    return sorted(buckets.items(), key=lambda kv: kv[0])


def _sketch_in_body(sk, body):
    try:
        if sk.getParentGeoFeatureGroup() == body:
            return True
    except Exception:
        pass
    return sk in getattr(body, "Group", [])


def _sketch_attached_to_slice_datum(sk):
    sup = getattr(sk, "AttachmentSupport", None) or getattr(sk, "Support", None)
    if not sup:
        return False
    for ref, _sub in sup:
        if ref is None:
            continue
        rn = getattr(ref, "Name", "") or ""
        if rn.startswith("DatumPlane_X"):
            return True
    return False


def _slice_sketches(doc, body):
    name_pat = re.compile(r"^Sketch_X_?-?\d+$")
    found = []
    for o in doc.Objects:
        if o.TypeId != "Sketcher::SketchObject":
            continue
        if not _sketch_in_body(o, body):
            continue
        if _sketch_attached_to_slice_datum(o) or name_pat.match(o.Name):
            found.append(o)
    found.sort(key=lambda sk: sk.Shape.BoundBox.XMin)
    return found


def _profile_edge(sk):
    eds = sk.Shape.Edges
    if len(eds) == 1:
        return eds[0]
    if len(eds) == 0:
        return None
    w = Part.Wire(eds)
    try:
        apx = w.approximate(1e-6, 1e-4, 25, 999)
        sh = apx.toShape()
        if sh.Edges:
            return sh.Edges[0]
    except Exception:
        pass
    return eds[0]


def _dedupe_consecutive_vectors(pts, tol_mm=0.02):
    if not pts:
        return pts
    out = [pts[0]]
    for p in pts[1:]:
        if (p - out[-1]).Length > tol_mm:
            out.append(p)
    return out


def _dedupe_slice_cloud_points(pts):
    """Remove consecutive (y,z) duplicates before fitting slice B-splines."""
    if not pts:
        return pts
    out = [pts[0]]
    for p in pts[1:]:
        q = out[-1]
        dy = abs(p.y - q.y)
        dz = abs(p.z - q.z)
        if dy > 1e-4 or dz > 1e-4:
            out.append(p)
    return out


def _common_y_interval_all_edges(sks):
    """Y range for guide stations.

    Strict overlap is max(ymins)..min(ymaxs) (every profile contains the interval).
    If one thin slice has a tiny Y span, that alone collapses the interval and Gordon
    guides only cover a narrow band (and Curves may miss intersections / crash).
    When overlap is much narrower than the combined slice span, use the full combined
    span instead; out-of-range Y then uses the chord between profile parametric ends.
    """
    ymins = []
    ymaxs = []
    for sk in sks:
        e = _profile_edge(sk)
        if e is None:
            return None
        bb = e.BoundBox
        ymins.append(bb.YMin)
        ymaxs.append(bb.YMax)
    y0 = max(ymins)
    y1 = min(ymaxs)
    span_inter = y1 - y0
    y_lo = min(ymins)
    y_hi = max(ymaxs)
    span_union = y_hi - y_lo
    if span_inter < Y_TOL_MM * 10.0:
        return None
    if span_union > 1e-6 and span_inter < 0.30 * span_union:
        App.Console.PrintWarning(
            "PointsToSurface: strict per-slice Y overlap %.4g..%.4g (width %.4g mm) is "
            "much smaller than combined span %.4g..%.4g (width %.4g mm). "
            "Using the combined span for guide stations so Gordon covers the terrain; "
            "slices with short Y extent will clamp at their Y ends.\n"
            % (y0, y1, span_inter, y_lo, y_hi, span_union)
        )
        return y_lo, y_hi
    return y0, y1


def _edge_y_min_max_points(edge):
    """Approximate points of minimum and maximum Y along the edge (for chord / rails)."""
    c = edge.Curve
    ta = edge.FirstParameter
    tb = edge.LastParameter
    n = 96
    best_lo = c.value(ta)
    best_hi = c.value(ta)
    ymin = best_lo.y
    ymax = best_hi.y
    for i in range(n):
        t = ta + (tb - ta) * i / (n - 1)
        p = c.value(t)
        if p.y < ymin:
            ymin = p.y
            best_lo = p
        if p.y > ymax:
            ymax = p.y
            best_hi = p
    return best_lo, best_hi


def _point_on_endpoint_chord_at_y(pa, pb, y_target):
    """Point in the slice plane on the infinite line through pa–pb (Y = y_target)."""
    dy = pb.y - pa.y
    if abs(dy) < Y_TOL_MM:
        return App.Vector(
            0.5 * (pa.x + pb.x),
            y_target,
            0.5 * (pa.z + pb.z),
        )
    t = (y_target - pa.y) / dy
    return App.Vector(
        pa.x + t * (pb.x - pa.x),
        pa.y + t * (pb.y - pa.y),
        pa.z + t * (pb.z - pa.z),
    )


def _point_on_edge_interior_at_y(edge, y_use):
    """Point on edge where Y ~= y_use; y_use must lie within edge.BoundBox Y range."""
    c = edge.Curve
    ta = edge.FirstParameter
    tb = edge.LastParameter
    n = 64
    ts = [ta + (tb - ta) * i / (n - 1) for i in range(n)]
    for i in range(n - 1):
        t0, t1 = ts[i], ts[i + 1]
        y0 = c.value(t0).y
        y1 = c.value(t1).y
        if (y0 - y_use) * (y1 - y_use) <= 0:
            for _ in range(48):
                tm = 0.5 * (t0 + t1)
                ym = c.value(tm).y
                if abs(ym - y_use) < Y_TOL_MM * 10.0:
                    return c.value(tm)
                if (y0 - y_use) * (ym - y_use) <= 0:
                    t1, y1 = tm, ym
                else:
                    t0, y0 = tm, ym
            return c.value(0.5 * (t0 + t1))
    best_t = ta
    best_e = 1e300
    for t in ts:
        e = abs(c.value(t).y - y_use)
        if e < best_e:
            best_e = e
            best_t = t
    return c.value(best_t)


def _guide_point_for_slice(edge, y_target, y_mm_cache=None):
    """Guide sample at this slice: on the profile at Y when possible; else on the Y-min–Y-max chord.

    y_mm_cache: optional dict edge id -> (p_y_min, p_y_max) from _edge_y_min_max_points.
    """
    bb = edge.BoundBox
    ymin = bb.YMin
    ymax = bb.YMax
    span = ymax - ymin
    tol = max(Y_TOL_MM * 10.0, 1e-6 * max(abs(ymin), abs(ymax), 1.0))
    eid = id(edge)
    if y_mm_cache is not None and eid in y_mm_cache:
        pa, pb = y_mm_cache[eid]
    else:
        pa, pb = _edge_y_min_max_points(edge)
        if y_mm_cache is not None:
            y_mm_cache[eid] = (pa, pb)
    if span < Y_TOL_MM * 10.0:
        return _point_on_endpoint_chord_at_y(pa, pb, y_target)
    if y_target < ymin - tol or y_target > ymax + tol:
        return _point_on_endpoint_chord_at_y(pa, pb, y_target)
    y_use = max(ymin, min(ymax, y_target))
    return _point_on_edge_interior_at_y(edge, y_use)


def _y_stations(y0, y1, step=None):
    if step is None:
        step = Y_STEP_MM
    if y1 < y0:
        y0, y1 = y1, y0
    ys = [y0]
    y = y0 + step
    while y < y1 - 1e-6:
        ys.append(y)
        y += step
    if abs(ys[-1] - y1) > 1e-3:
        ys.append(y1)
    return ys


def _import_gordon():
    mod = importlib.import_module("freecad.Curves.gordonFP")
    return mod.gordonFP, mod.gordonVP


def _move_into_body(body, obj, after_feature=None):
    if obj is None or body is None:
        return False
    try:
        if obj in list(getattr(body, "Group", []) or []):
            return True
    except Exception:
        pass
    add = getattr(body, "addObject", None)
    if callable(add):
        try:
            add(obj)
            return True
        except Exception:
            pass
    ins = getattr(body, "insertObject", None)
    if callable(ins):
        refs = []
        if after_feature is not None:
            refs.append(after_feature)
        refs.append(None)
        for ref in refs:
            for tail in (True, False):
                try:
                    ins(obj, ref, tail)
                    return True
                except Exception:
                    continue
    try:
        g = list(getattr(body, "Group", []) or [])
        if obj not in g:
            g.append(obj)
            body.Group = g
        return True
    except Exception as exc:
        App.Console.PrintWarning(
            "PointsToSurface: could not add %s to Body (%s).\n"
            % (getattr(obj, "Name", "?"), exc)
        )
        return False


def _sorted_slice_sketches(sketches):
    return sorted(sketches, key=lambda sk: sk.Shape.BoundBox.XMin)


def _build_profile_edges(sketches):
    sks = _sorted_slice_sketches(sketches)
    edges = []
    for sk in sks:
        if not sk.Shape or sk.Shape.isNull():
            continue
        e = _profile_edge(sk)
        if e is not None:
            edges.append(e)
    return edges


def _mild_bspline_edge(edge):
    """Re-sample edge and interpolate; reduces kinks that make Curves reparam return None."""
    if edge is None or edge.Length < 1e-8:
        return None
    try:
        c = edge.Curve
        ta = edge.FirstParameter
        tb = edge.LastParameter
        n = max(16, min(96, int(edge.Length / 2.5) + 8))
        pts = [c.value(ta + (tb - ta) * i / (n - 1)) for i in range(n)]
        pts = _dedupe_consecutive_vectors(pts, tol_mm=0.02)
        if len(pts) < 2:
            return edge
        bs = Part.BSplineCurve()
        bs.interpolate(pts, False)
        ge = _to_single_guide_edge(bs.toShape())
        return ge if (ge is not None and ge.Length >= 1e-6) else edge
    except Exception:
        return edge


def _to_single_guide_edge(sh):
    """Curves gordonFP uses Sources[0].Shape.Edges — one edge per guide, or Gordon breaks."""
    if sh is None or sh.isNull():
        return None
    eds = sh.Edges
    if len(eds) == 1:
        return eds[0]
    if not eds:
        return None
    w = Part.Wire(eds)
    try:
        apx = w.approximate(1e-6, 1e-4, 25, 999)
        sh2 = apx.toShape()
        if sh2.Edges:
            return sh2.Edges[0]
    except Exception:
        pass
    try:
        v0 = w.Vertexes[0].Point
        v1 = w.Vertexes[-1].Point
        if v0.distanceToPoint(v1) < 1e-8:
            return None
        return Part.makeLine(v0, v1)
    except Exception:
        return None


def _build_guide_shapes(sketches, y_step):
    sks = _sorted_slice_sketches(sketches)
    if len(sks) < 2:
        return []
    common = _common_y_interval_all_edges(sks)
    if common is not None:
        y0, y1 = common
    else:
        bb = sks[0].Shape.BoundBox
        for sk in sks[1:]:
            bb.add(sk.Shape.BoundBox)
        y0 = bb.YMin
        y1 = bb.YMax
        App.Console.PrintWarning(
            "PointsToSurface: slice Y ranges barely overlap — guides use full Y span; "
            "Gordon may be unstable. Prefer denser points per slice on shared Y extent.\n"
        )
    stations = _y_stations(y0, y1, float(y_step))
    shapes = []
    y_mm_cache = {}
    for y in stations:
        pts = []
        for sk in sks:
            edge = _profile_edge(sk)
            if edge is None:
                return []
            pts.append(_guide_point_for_slice(edge, y, y_mm_cache))
        pts = _dedupe_consecutive_vectors(pts, tol_mm=0.05)
        if len(pts) < 2:
            continue
        try:
            bs = Part.BSplineCurve()
            bs.interpolate(pts, False)
            sh = bs.toShape()
        except Exception:
            sh = Part.makePolygon(pts)
        ge = _to_single_guide_edge(sh)
        if ge is None or ge.Length < 1e-6:
            continue
        ge = _mild_bspline_edge(ge)
        if ge is None or ge.Length < 1e-6:
            continue
        shapes.append(ge)
    return shapes


class _GordonProfilesDriverFP:
    def __init__(self, obj):
        obj.addProperty(
            "App::PropertyLinkList",
            "SliceSketches",
            "Links",
            "Cross-section sketches (datum slice sketches)",
        )
        obj.Proxy = self

    def execute(self, obj):
        sks = obj.SliceSketches
        if not sks:
            obj.Shape = Part.Shape()
            return
        edges = _build_profile_edges(sks)
        if len(edges) < 2:
            obj.Shape = Part.Shape()
            return
        obj.Shape = Part.Compound(edges)

    def dumps(self):
        return None

    def loads(self, state):
        return None


class _GordonGuidesDriverFP:
    def __init__(self, obj):
        obj.addProperty(
            "App::PropertyLinkList",
            "SliceSketches",
            "Links",
            "Same slice sketches as profile driver",
        )
        obj.addProperty(
            "App::PropertyFloat",
            "YStep",
            "Grid",
            "Guide spacing along Y (mm)",
        )
        obj.YStep = float(Y_STEP_MM)
        obj.Proxy = self

    def execute(self, obj):
        sks = obj.SliceSketches
        step = float(getattr(obj, "YStep", Y_STEP_MM) or Y_STEP_MM)
        if not sks or step <= 0:
            obj.Shape = Part.Shape()
            return
        shapes = _build_guide_shapes(sks, step)
        if len(shapes) < 2:
            obj.Shape = Part.Shape()
            return
        obj.Shape = Part.Compound(shapes)

    def dumps(self):
        return None

    def loads(self, state):
        return None


class _DriverVP:
    def __init__(self, vobj):
        vobj.Proxy = self

    def attach(self, vobj):
        self.Object = vobj.Object

    def dumps(self):
        return None

    def loads(self, state):
        return None


def _run_cross_sections(doc, body):
    points_obj = _pick_points_object(doc)
    if points_obj is None:
        return False

    vecs = _extract_points(points_obj)
    if len(vecs) < 2:
        App.Console.PrintError("PointsToSurface: need at least two points.\n")
        return False

    doc.recompute()
    groups = _group_by_x(vecs)
    created = 0
    skipped_single = 0
    for _xkey, pts in groups:
        pts_sorted = _dedupe_slice_cloud_points(sorted(pts, key=lambda p: (p.y, p.z)))
        if len(pts_sorted) < 2:
            skipped_single += 1
            continue

        slice_x = sum(p.x for p in pts_sorted) / len(pts_sorted)
        tag = "X%05d" % int(round(slice_x))

        plane = _new_partdesign_plane(body, "DatumPlane_" + tag)
        plane.AttachmentSupport = [(body.Origin, "")]
        plane.MapMode = "ObjectYZ"
        plane.AttachmentOffset = App.Placement(
            App.Vector(0.0, 0.0, slice_x),
            App.Rotation(App.Vector(0.0, 0.0, 1.0), 0.0),
        )
        doc.recompute()
        vo = getattr(plane, "ViewObject", None)
        if vo is not None:
            vo.Visibility = False

        sketch = body.newObject("Sketcher::SketchObject", "Sketch_" + tag)
        sketch.MapMode = "FlatFace"
        if hasattr(sketch, "AttachmentSupport"):
            sketch.AttachmentSupport = [(plane, ("",))]
        else:
            sketch.Support = [(plane, ("",))]
        doc.recompute()

        g3d = [App.Vector(slice_x, p.y, p.z) for p in pts_sorted]
        inv = sketch.Placement.inverse()
        pts2d = []
        for g in g3d:
            loc = inv.multVec(g)
            pts2d.append(App.Vector(loc.x, loc.y, 0.0))

        if len(pts2d) == 2:
            sketch.addGeometry(Part.LineSegment(pts2d[0], pts2d[1]), False)
        else:
            try:
                bs = Part.BSplineCurve()
                bs.interpolate(pts2d, False)
                gid = sketch.addGeometry(bs, False)
                _expose = getattr(sketch, "exposeInternalGeometry", None) or getattr(
                    sketch, "ExposeInternalGeometry", None
                )
                if _expose is not None:
                    try:
                        _expose(gid)
                    except Exception:
                        pass
            except Exception:
                for i in range(len(pts2d) - 1):
                    sketch.addGeometry(
                        Part.LineSegment(pts2d[i], pts2d[i + 1]), False
                    )
        doc.recompute()
        created += 1

    App.Console.PrintMessage(
        "PointsToSurface: created %d slice(s) on %s.\n"
        % (created, body.Label)
    )
    if skipped_single:
        App.Console.PrintMessage(
            "PointsToSurface: skipped %d X-group(s) with only one point (no sketch).\n"
            % (skipped_single,)
        )
    return True


def _run_gordon_surface(doc, body, y_step_mm):
    sketches = _slice_sketches(doc, body)
    if len(sketches) < 2:
        App.Console.PrintError(
            "PointsToSurface: need at least two slice sketches "
            "(DatumPlane_X* on the Body).\n"
        )
        return False

    doc.recompute()

    try:
        gordon_fp_cls, gordon_vp_cls = _import_gordon()
    except Exception as exc:
        App.Console.PrintError(
            "PointsToSurface: Curves workbench not available (%s).\n" % (exc,)
        )
        return False

    for sk in sketches:
        if not sk.Shape or sk.Shape.isNull():
            App.Console.PrintError(
                "PointsToSurface: sketch %s has no shape.\n" % (sk.Name,)
            )
            return False
        if _profile_edge(sk) is None:
            App.Console.PrintError(
                "PointsToSurface: no edges in sketch %s.\n" % (sk.Name,)
            )
            return False

    prof_edges = _build_profile_edges(sketches)
    guide_shapes = _build_guide_shapes(sketches, float(y_step_mm))
    if len(prof_edges) < 2 or len(guide_shapes) < 2:
        App.Console.PrintError(
            "PointsToSurface: need at least two profiles and two guides.\n"
        )
        return False

    common = _common_y_interval_all_edges(_sorted_slice_sketches(sketches))
    if common is not None:
        y0, y1 = common
    else:
        bb = sketches[0].Shape.BoundBox
        for sk in sketches[1:]:
            bb.add(sk.Shape.BoundBox)
        y0 = bb.YMin
        y1 = bb.YMax

    gname = "GordonSurface_Guides"
    pname = "GordonSurface_Profiles"
    gordname = "GordonSurface"
    for n in (gordname, gname, pname):
        old = doc.getObject(n)
        if old is not None:
            doc.removeObject(old.Name)

    guides_obj = doc.addObject("Part::FeaturePython", gname)
    _GordonGuidesDriverFP(guides_obj)
    _DriverVP(guides_obj.ViewObject)

    profiles_obj = doc.addObject("Part::FeaturePython", pname)
    _GordonProfilesDriverFP(profiles_obj)
    _DriverVP(profiles_obj.ViewObject)

    gordon = doc.addObject("Part::FeaturePython", gordname)
    gordon_fp_cls(gordon)
    gordon_vp_cls(gordon.ViewObject)
    if hasattr(gordon, "Tol3D"):
        gordon.Tol3D = max(float(getattr(gordon, "Tol3D", 0.01) or 0.01), 1.0)
    if hasattr(gordon, "Tol2D"):
        gordon.Tol2D = max(float(getattr(gordon, "Tol2D", 0.0) or 0.0), 1e-4)
    if hasattr(gordon, "MaxCtrlPts"):
        n_p = len(sketches)
        n_g = len(guide_shapes)
        gordon.MaxCtrlPts = min(100, max(28, max(n_p, n_g) * 3 + 12))

    sks_sorted = _sorted_slice_sketches(sketches)
    anchor = sks_sorted[-1] if sks_sorted else None
    for o in (guides_obj, profiles_obj, gordon):
        if not _move_into_body(body, o, anchor):
            App.Console.PrintError(
                "PointsToSurface: failed to add %s to Body.\n" % (o.Name,)
            )
            return False

    guides_obj.SliceSketches = sketches
    guides_obj.YStep = float(y_step_mm)
    profiles_obj.SliceSketches = sketches
    gordon.Sources = [guides_obj, profiles_obj]
    doc.recompute()

    gv = getattr(guides_obj, "ViewObject", None)
    pv = getattr(profiles_obj, "ViewObject", None)
    if gv is not None:
        gv.Visibility = False
    if pv is not None:
        pv.Visibility = False

    App.Console.PrintMessage(
        "PointsToSurface: %d profiles, %d guides (Y every %g mm, %g..%g), Gordon=%s.\n"
        % (
            len(prof_edges),
            len(guide_shapes),
            float(y_step_mm),
            y0,
            y1,
            gordon.Name,
        )
    )
    App.Console.PrintMessage(
        "Curves WB: Sources[0]=guides (X-running), Sources[1]=profiles (slices).\n"
    )
    App.Console.PrintMessage(
        "Parametric: edit slice sketches, then F5. Adjust YStep on GordonSurface_Guides.\n"
    )
    return True


def main():
    doc = App.activeDocument()
    if doc is None:
        App.Console.PrintError("PointsToSurface: no active document.\n")
        return

    body = _active_body(doc, create_if_missing=True)
    if body is None:
        App.Console.PrintError(
            "PointsToSurface: no PartDesign Body (activate one in the tree).\n"
        )
        return

    y_step = _resolve_y_step_mm()
    if y_step is None:
        App.Console.PrintMessage("PointsToSurface: cancelled (Y step).\n")
        return
    if not _run_cross_sections(doc, body):
        return
    if not _run_gordon_surface(doc, body, y_step):
        return


main()
